NAS-MIB DEFINITIONS ::= BEGIN

   IMPORTS
      enterprises, Counter, TimeTicks
         FROM RFC1155-SMI
      Integer32, Counter32, IpAddress, Unsigned32, Counter64
         FROM SNMPv2-SMI
      OBJECT-TYPE
         FROM RFC-1212
      TRAP-TYPE
         FROM RFC-1215;

      -- From RFC-1213 (MIB-II)
      DisplayString ::= OCTET STRING

    storage     OBJECT IDENTIFIER ::= { enterprises 24681 }
    storageSystem        OBJECT IDENTIFIER ::= { storage 1 }

 -- Frame Relay Multiplexer MIB groups
 -- system Event
   SystemEventMsg        OBJECT IDENTIFIER ::= { storageSystem 1 }

 -- system event
   EventInformMsg OBJECT-TYPE
      SYNTAX  DisplayString
      ACCESS  read-only
      STATUS  current
      DESCRIPTION
         "Information event of NAS system."
     ::= { SystemEventMsg 101 }

   EventWarningMsg OBJECT-TYPE
      SYNTAX  DisplayString
      ACCESS  read-only
      STATUS  current
      DESCRIPTION
         "Warning event of NAS system."
      ::= { SystemEventMsg 102 }

   EventErrorMsg OBJECT-TYPE
      SYNTAX  DisplayString
      ACCESS  read-only
      STATUS  current
      DESCRIPTION
         "Error event of NAS system."
      ::= { SystemEventMsg 103 }

	SystemTraps OBJECT IDENTIFIER ::= { storageSystem  10 }
	
	EventInform TRAP-TYPE
		ENTERPRISE SystemTraps    
		VARIABLES { EventInformMsg }
		DESCRIPTION
			"Info: %s"
		::=  1

	EventWarning TRAP-TYPE
		ENTERPRISE SystemTraps    
		VARIABLES { EventWarningMsg }
		DESCRIPTION 
			"Warn: %s"
		::=  2

	EventError TRAP-TYPE
		ENTERPRISE SystemTraps
		VARIABLES { EventErrorMsg }
		DESCRIPTION 
			"Error: %s"
		::=  4

 -- system inform
	SystemInfo        OBJECT IDENTIFIER ::= { storageSystem 2 }

	SystemCPU-Usage OBJECT-TYPE
		SYNTAX DisplayString
    	MAX-ACCESS read-only
	    STATUS     current
    	DESCRIPTION
			"System CPU usage"
		::= { SystemInfo 1 }
	SystemTotalMem OBJECT-TYPE
		SYNTAX DisplayString
    	MAX-ACCESS read-only
	    STATUS     current
    	DESCRIPTION
			"System total memory"
		::= { SystemInfo 2 }
	SystemFreeMem OBJECT-TYPE
		SYNTAX DisplayString
    	MAX-ACCESS read-only
	    STATUS     current
    	DESCRIPTION
			"System free memory"
		::= { SystemInfo 3 }
	SystemUptime OBJECT-TYPE
    	SYNTAX     TimeTicks
    	MAX-ACCESS read-only
	    STATUS     current
    	DESCRIPTION
        	"The amount of time since this host was last
	        initialized.  Note that this is different from
    	    sysUpTime in the SNMPv2-MIB [RFC1907] because
        	sysUpTime is the uptime of the network management
	        portion of the system."
    	::= { SystemInfo 4 }
	CPU-Temperature OBJECT-TYPE
		SYNTAX DisplayString
    	MAX-ACCESS read-only
	    STATUS     current
    	DESCRIPTION
			"CPU temperature"
		::= { SystemInfo 5 }
	SystemTemperature OBJECT-TYPE
		SYNTAX DisplayString
    	MAX-ACCESS read-only
	    STATUS     current
    	DESCRIPTION
			"System temperature"
		::= { SystemInfo 6 }

IfNumber OBJECT-TYPE
    SYNTAX  INTEGER
    ACCESS  read-only
    STATUS  mandatory
    DESCRIPTION
            "The number of network interfaces (regardless of
            their current state) present on this system."
    ::= { SystemInfo 8 }
SystemIfTable OBJECT-TYPE
    SYNTAX  SEQUENCE OF IfEntryDef
    ACCESS  not-accessible
    STATUS  mandatory
    DESCRIPTION
            "A list of interface entries.  The number of
            entries is given by the value of IfNumber."
    ::= { SystemInfo 9 }
IfEntry OBJECT-TYPE
    SYNTAX  IfEntryDef
    ACCESS  not-accessible
    STATUS  mandatory
    DESCRIPTION
            "An interface entry containing objects at the
            subnetwork layer and below for a particular
            interface."
    INDEX   { IfIndex }
    ::= { SystemIfTable 1 }
IfEntryDef ::=
    SEQUENCE {
        IfIndex
            INTEGER,
        IfDescr
            DisplayString,
		IfPacketsReceived
            Counter,
		IfPacketsSent
            Counter,
		IfErrorPackets
            Counter
	}
IfIndex OBJECT-TYPE
    SYNTAX  INTEGER
    ACCESS  read-only
    STATUS  mandatory
    DESCRIPTION
            "A unique value for each interface.  Its value
            ranges between 1 and the value of IfNumber.  The
            value for each interface must remain constant at
            least from one re-initialization of the entity's
            network management system to the next re-
            initialization."
    ::= { IfEntry 1 }
IfDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { IfEntry 2 }
IfPacketsReceived OBJECT-TYPE
    SYNTAX  Counter
    ACCESS  read-only
    STATUS  mandatory
    DESCRIPTION
            "System packets received."
    ::= { IfEntry 3 }
IfPacketsSent OBJECT-TYPE
    SYNTAX  Counter
    ACCESS  read-only
    STATUS  mandatory
    DESCRIPTION
            "System packets sent."
    ::= { IfEntry 4 }
IfErrorPackets OBJECT-TYPE
    SYNTAX  Counter
    ACCESS  read-only
    STATUS  mandatory
    DESCRIPTION
            "System error packets."
    ::= { IfEntry 5 }

HdNumber OBJECT-TYPE
    SYNTAX  INTEGER
    ACCESS  read-only
    STATUS  mandatory
    DESCRIPTION
            "The number of hard drive slots."
    ::= { SystemInfo 10 }
SystemHdTable OBJECT-TYPE
    SYNTAX  SEQUENCE OF HdEntryDef
    ACCESS  not-accessible
    STATUS  mandatory
    DESCRIPTION
            "A list of interface entries.  The number of
            entries is given by the value of HdNumber."
    ::= { SystemInfo 11 }
HdEntry OBJECT-TYPE
    SYNTAX  HdEntryDef
    ACCESS  not-accessible
    STATUS  mandatory
    DESCRIPTION
            "An interface entry containing objects at the
            subnetwork layer and below for a particular
            interface."
    INDEX   { HdIndex }
    ::= { SystemHdTable 1 }
HdEntryDef ::=
    SEQUENCE {
        HdIndex
            INTEGER,
        HdDescr
            DisplayString,
        HdTemperature
            DisplayString,
        HdStatus
            INTEGER,
	HdModel DisplayString,
	HdCapacity DisplayString,
	HdSmartInfo DisplayString
	}
HdIndex OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { HdEntry 1 }
HdDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { HdEntry 2 }
HdTemperature OBJECT-TYPE
    SYNTAX  DisplayString
    ACCESS  read-only
    STATUS  mandatory
    DESCRIPTION
            "Hard disk temperature."
    ::= { HdEntry 3 }
HdStatus OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { HdEntry 4 }
HdModel OBJECT-TYPE
    SYNTAX  DisplayString
    ACCESS  read-only
    STATUS  mandatory
    DESCRIPTION "Hard disk model."
    ::= { HdEntry 5 }
HdCapacity OBJECT-TYPE
    SYNTAX  DisplayString
    ACCESS  read-only
    STATUS  mandatory
    DESCRIPTION "Hard disk capacity."
    ::= { HdEntry 6 }
HdSmartInfo OBJECT-TYPE
    SYNTAX  DisplayString
    ACCESS  read-only
    STATUS  mandatory
    DESCRIPTION "Hard disk SMART information."
    ::= { HdEntry 7 }

	ModelName OBJECT-TYPE
		SYNTAX DisplayString
    	MAX-ACCESS read-only
	    STATUS     current
    	DESCRIPTION
			"Model name"
		::= { SystemInfo 12 }
	HostName OBJECT-TYPE
		SYNTAX DisplayString
    	MAX-ACCESS read-only
	    STATUS     current
    	DESCRIPTION
			"Model name"
		::= { SystemInfo 13 }

SysFanNumber OBJECT-TYPE
    SYNTAX  INTEGER
    ACCESS  read-only
    STATUS  mandatory
    DESCRIPTION
            "The number of system fan (regardless of
            their current state) present on this system."
    ::= { SystemInfo 14 }
SystemFanTable OBJECT-TYPE
    SYNTAX  SEQUENCE OF SysFanEntryDef
    ACCESS  not-accessible
    STATUS  mandatory
    DESCRIPTION
            "A list of interface entries.  The number of
            entries is given by the value of SysFanNumber."
    ::= { SystemInfo 15 }
SysFanEntry OBJECT-TYPE
    SYNTAX  SysFanEntryDef
    ACCESS  not-accessible
    STATUS  mandatory
    DESCRIPTION
            "An system fan entry containing objects at the
            subnetwork layer and below for a particular
            interface."
    INDEX   { SysFanIndex }
    ::= { SystemFanTable 1 }
SysFanEntryDef ::=
    SEQUENCE {
        SysFanIndex
            INTEGER,
        SysFanDescr
            DisplayString,
		SysFanSpeed
            DisplayString
	}
SysFanIndex OBJECT-TYPE
    SYNTAX  INTEGER
    ACCESS  read-only
    STATUS  mandatory
    DESCRIPTION
            "A unique value for each system fan. Its value
            ranges between 1 and the value of SysFanNumber.  The
            value for each interface must remain constant at
            least from one re-initialization of the entity's
            network management system to the next re-
            initialization."
    ::= { SysFanEntry 1 }
SysFanDescr OBJECT-TYPE
    SYNTAX  DisplayString (SIZE (0..255))
    ACCESS  read-only
    STATUS  mandatory
    DESCRIPTION
            "A textual string containing information about the
            interface.  This string should include the name of
            the manufacturer, the product name and the version
            of the hardware interface."
    ::= { SysFanEntry 2 }
SysFanSpeed OBJECT-TYPE
    SYNTAX  DisplayString (SIZE (0..255))
    ACCESS  read-only
    STATUS  mandatory
    DESCRIPTION
            "System fan speed."
    ::= { SysFanEntry 3 }

SysVolumeNumber OBJECT-TYPE
    SYNTAX  INTEGER
    ACCESS  read-only
    STATUS  mandatory
    DESCRIPTION
            "The number of system volumes (regardless of
            their current state) present on this system."
    ::= { SystemInfo 16 }
SystemVolumeTable OBJECT-TYPE
    SYNTAX  SEQUENCE OF SysVolumeEntryDef
    ACCESS  not-accessible
    STATUS  mandatory
    DESCRIPTION
            "A list of volume entries.  The number of
            entries is given by the value of SysVolumeNumber."
    ::= { SystemInfo 17 }
SysVolumeEntry OBJECT-TYPE
    SYNTAX  SysVolumeEntryDef
    ACCESS  not-accessible
    STATUS  mandatory
    DESCRIPTION
            "An system volume entry"
    INDEX   { SysVolumeIndex }
    ::= { SystemVolumeTable 1 }
SysVolumeEntryDef ::=
    SEQUENCE {
        SysVolumeIndex	INTEGER,
        SysVolumeDescr	DisplayString,
	SysVolumeFS	DisplayString,
	SysVolumeTotalSize	DisplayString,
	SysVolumeFreeSize	DisplayString,
	SysVolumeStatus	DisplayString
	}
SysVolumeIndex OBJECT-TYPE
    SYNTAX  INTEGER
    ACCESS  read-only
    STATUS  mandatory
    DESCRIPTION
            "A unique value for each system volume. Its value
            ranges between 1 and the value of SysVolumeNumber.  The
            value for each volume must remain constant at
            least from one re-initialization of the entity's
            volume system to the next re-initialization."
    ::= { SysVolumeEntry 1 }
SysVolumeDescr OBJECT-TYPE
    SYNTAX  DisplayString (SIZE (0..255))
    ACCESS  read-only
    STATUS  mandatory
    DESCRIPTION	"A textual string containing information about the volume."
    ::= { SysVolumeEntry 2 }
SysVolumeFS OBJECT-TYPE
    SYNTAX  DisplayString (SIZE (0..15))
    ACCESS  read-only
    STATUS  mandatory
    DESCRIPTION	"System Volume file system."
    ::= { SysVolumeEntry 3 }
SysVolumeTotalSize OBJECT-TYPE
    SYNTAX  DisplayString (SIZE (0..15))
    ACCESS  read-only
    STATUS  mandatory
    DESCRIPTION	"System Volume total size."
    ::= { SysVolumeEntry 4 }
SysVolumeFreeSize OBJECT-TYPE
    SYNTAX  DisplayString (SIZE (0..15))
    ACCESS  read-only
    STATUS  mandatory
    DESCRIPTION	"System Volume free size."
    ::= { SysVolumeEntry 5 }
SysVolumeStatus OBJECT-TYPE
    SYNTAX  DisplayString (SIZE (0..255))
    ACCESS  read-only
    STATUS  mandatory
    DESCRIPTION	"System Volume status."
    ::= { SysVolumeEntry 6 }

JBODInfo OBJECT-TYPE
    SYNTAX  DisplayString
    ACCESS  read-only
    STATUS  mandatory
    DESCRIPTION
            "The bitmap  of JBOD (regardless of
            their current state) present on this system."
    ::= { SystemInfo 18 }
    
JBODBitmap OBJECT-TYPE
    SYNTAX  DisplayString
    ACCESS  read-only
    STATUS  mandatory
    DESCRIPTION
            "The bitmap  of JBOD (regardless of
            their current state) present on this system."
    ::= { JBODInfo 1 }
    
    
JBODInfos OBJECT-TYPE
    SYNTAX  SEQUENCE OF HdEntryDef
    ACCESS  not-accessible
    STATUS  mandatory
    DESCRIPTION
            "A list of interface entries.  The number of
            entries is given by the value of IfNumber."
    ::= { JBODInfo 2 }
JBODInfosEntry OBJECT-TYPE
    SYNTAX  HdEntryDef
    ACCESS  not-accessible
    STATUS  mandatory
    DESCRIPTION
            "An interface entry containing objects at the
            subnetwork layer and below for a particular
            interface."
    INDEX   { JBODid }
    ::= { JBODInfos 1 }
JBODInfosEntryDef ::=
    SEQUENCE {
        JBODid  INTEGER,
        JBODHdNumber INTEGER
	}
JBODid OBJECT-TYPE
    SYNTAX  INTEGER
    ACCESS  read-only
    STATUS  mandatory
    DESCRIPTION
            "A unique value for each JBOD. Its value
            ranges between 1 and the value of IfNumber.  The
            value for each interface must remain constant at
            least from one re-initialization of the entity's
            network management system to the next re-
            initialization."
    ::= { JBODInfosEntry 1 }
    
JBODHdNumber OBJECT-TYPE
    SYNTAX  INTEGER
    ACCESS  read-only
    STATUS  mandatory
    DESCRIPTION
            "JBOD Disk port."
    ::= { JBODInfosEntry 2 }
    
JBODHdTable1 OBJECT-TYPE
    SYNTAX  SEQUENCE OF HdEntryDef
    ACCESS  not-accessible
    STATUS  mandatory
    DESCRIPTION
            "A list of interface entries.  The number of
            entries is given by the value of IfNumber."
    ::= { JBODInfo 3 }
JBODHdEntry1 OBJECT-TYPE
    SYNTAX  HdEntryDef
    ACCESS  not-accessible
    STATUS  mandatory
    DESCRIPTION
            "An interface entry containing objects at the
            subnetwork layer and below for a particular
            interface."
    INDEX   { JBODHdIndex1 }
    ::= { JBODHdTable1 1 }
JBODHdEntry1Def ::=
    SEQUENCE {
        JBODHdIndex1  INTEGER,
        JBODHdDescr1 DisplayString,
        JBODHdTemperature1 DisplayString,
        JBODHdStatus1 INTEGER,
        JBODHdModel1 DisplayString,
        JBODHdCapacity1 DisplayString,
        JBODHdSmartInfo1 DisplayString
	}
JBODHdIndex1 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry1 1 }
JBODHdDescr1 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry1 2 }
JBODHdTemperature1 OBJECT-TYPE
    SYNTAX  DisplayString
    ACCESS  read-only
    STATUS  mandatory
    DESCRIPTION
            "Hard disk temperature."
    ::= { JBODHdEntry1 3 }
JBODHdStatus1 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry1 4 }
JBODHdModel1 OBJECT-TYPE
    SYNTAX  DisplayString
    ACCESS  read-only
    STATUS  mandatory
    DESCRIPTION "Hard disk model."
    ::= { JBODHdEntry1 5 }
JBODHdCapacity1 OBJECT-TYPE
    SYNTAX  DisplayString
    ACCESS  read-only
    STATUS  mandatory
    DESCRIPTION "Hard disk capacity."
    ::= { JBODHdEntry1 6 }
JBODHdSmartInfo1 OBJECT-TYPE
    SYNTAX  DisplayString
    ACCESS  read-only
    STATUS  mandatory
    DESCRIPTION "Hard disk SMART information."
    ::= { JBODHdEntry1 7 }
    
JBODHdTable2 OBJECT-TYPE
    SYNTAX  SEQUENCE OF HdEntryDef
    ACCESS  not-accessible
    STATUS  mandatory
    DESCRIPTION
            "A list of interface entries.  The number of
            entries is given by the value of IfNumber."
    ::= { JBODInfo 4}
JBODHdEntry2 OBJECT-TYPE
    SYNTAX  HdEntryDef
    ACCESS  not-accessible
    STATUS  mandatory
    DESCRIPTION
            "An interface entry containing objects at the
            subnetwork layer and below for a particular
            interface."
    INDEX   { JBODHdIndex2 }
    ::= { JBODHdTable2 1 }
JBODHdEntry2Def ::=
    SEQUENCE {
        JBODHdIndex2  INTEGER,
        JBODHdDescr2  DisplayString,
        JBODHdTemperature2  DisplayString,
        JBODHdStatus2  INTEGER,
        JBODHdModel2  DisplayString,
        JBODHdCapacity2  DisplayString,
        JBODHdSmartInfo2  DisplayString
	}
JBODHdIndex2  OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry2  1 }
JBODHdDescr2  OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry2  2 }
JBODHdTemperature2  OBJECT-TYPE
    SYNTAX  DisplayString
    ACCESS  read-only
    STATUS  mandatory
    DESCRIPTION
            "Hard disk temperature."
    ::= { JBODHdEntry2  3 }
JBODHdStatus2  OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry2  4 }
JBODHdModel2  OBJECT-TYPE
    SYNTAX  DisplayString
    ACCESS  read-only
    STATUS  mandatory
    DESCRIPTION "Hard disk model."
    ::= { JBODHdEntry2  5 }
JBODHdCapacity2  OBJECT-TYPE
    SYNTAX  DisplayString
    ACCESS  read-only
    STATUS  mandatory
    DESCRIPTION "Hard disk capacity."
    ::= { JBODHdEntry2  6 }
JBODHdSmartInfo2  OBJECT-TYPE
    SYNTAX  DisplayString
    ACCESS  read-only
    STATUS  mandatory
    DESCRIPTION "Hard disk SMART information."
    ::= { JBODHdEntry2  7 }
    
JBODHdTable3 OBJECT-TYPE
    SYNTAX  SEQUENCE OF HdEntryDef
    ACCESS  not-accessible
    STATUS  mandatory
    DESCRIPTION
            "A list of interface entries.  The number of
            entries is given by the value of IfNumber."
    ::= { JBODInfo 5 }
    
JBODHdEntry3 OBJECT-TYPE
    SYNTAX  HdEntryDef
    ACCESS  not-accessible
    STATUS  mandatory
    DESCRIPTION
            "An interface entry containing objects at the
            subnetwork layer and below for a particular
            interface."
    INDEX   { JBODHdIndex3 }
    ::= { JBODHdTable3 1 }
JBODHdEntry3Def ::=
    SEQUENCE {
        JBODHdIndex3  INTEGER,
        JBODHdDescr3 DisplayString,
        JBODHdTemperature3 DisplayString,
        JBODHdStatus3 INTEGER,
        JBODHdModel3 DisplayString,
        JBODHdCapacity3 DisplayString,
        JBODHdSmartInfo3 DisplayString
	}
JBODHdIndex3 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry3 1 }
JBODHdDescr3 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry3 2 }
JBODHdTemperature3 OBJECT-TYPE
    SYNTAX  DisplayString
    ACCESS  read-only
    STATUS  mandatory
    DESCRIPTION
            "Hard disk temperature."
    ::= { JBODHdEntry3 3 }
JBODHdStatus3 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry3 4 }
JBODHdModel3 OBJECT-TYPE
    SYNTAX  DisplayString
    ACCESS  read-only
    STATUS  mandatory
    DESCRIPTION "Hard disk model."
    ::= { JBODHdEntry3 5 }
JBODHdCapacity3 OBJECT-TYPE
    SYNTAX  DisplayString
    ACCESS  read-only
    STATUS  mandatory
    DESCRIPTION "Hard disk capacity."
    ::= { JBODHdEntry3 6 }
JBODHdSmartInfo3 OBJECT-TYPE
    SYNTAX  DisplayString
    ACCESS  read-only
    STATUS  mandatory
    DESCRIPTION "Hard disk SMART information."
    ::= { JBODHdEntry3 7 }
    
JBODHdTable4 OBJECT-TYPE
    SYNTAX  SEQUENCE OF HdEntryDef
    ACCESS  not-accessible
    STATUS  mandatory
    DESCRIPTION
            "A list of interface entries.  The number of
            entries is given by the value of IfNumber."
    ::= { JBODInfo 6 }
    
JBODHdEntry4 OBJECT-TYPE
    SYNTAX  HdEntryDef
    ACCESS  not-accessible
    STATUS  mandatory
    DESCRIPTION
            "An interface entry containing objects at the
            subnetwork layer and below for a particular
            interface."
    INDEX   { JBODHdIndex4 }
    ::= { JBODHdTable4 1 }
JBODHdEntry4Def ::=
    SEQUENCE {
        JBODHdIndex4  INTEGER,
        JBODHdDescr4 DisplayString,
        JBODHdTemperature4 DisplayString,
        JBODHdStatus4 INTEGER,
        JBODHdModel4 DisplayString,
        JBODHdCapacity4 DisplayString,
        JBODHdSmartInfo4 DisplayString
	}
JBODHdIndex4 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry4 1 }
JBODHdDescr4 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry4 2 }
JBODHdTemperature4 OBJECT-TYPE
    SYNTAX  DisplayString
    ACCESS  read-only
    STATUS  mandatory
    DESCRIPTION
            "Hard disk temperature."
    ::= { JBODHdEntry4 3 }
JBODHdStatus4 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry4 4 }
JBODHdModel4 OBJECT-TYPE
    SYNTAX  DisplayString
    ACCESS  read-only
    STATUS  mandatory
    DESCRIPTION "Hard disk model."
    ::= { JBODHdEntry4 5 }
JBODHdCapacity4 OBJECT-TYPE
    SYNTAX  DisplayString
    ACCESS  read-only
    STATUS  mandatory
    DESCRIPTION "Hard disk capacity."
    ::= { JBODHdEntry4 6 }
JBODHdSmartInfo4 OBJECT-TYPE
    SYNTAX  DisplayString
    ACCESS  read-only
    STATUS  mandatory
    DESCRIPTION "Hard disk SMART information."
    ::= { JBODHdEntry4 7 }
    
JBODHdTable5 OBJECT-TYPE
    SYNTAX  SEQUENCE OF HdEntryDef
    ACCESS  not-accessible
    STATUS  mandatory
    DESCRIPTION
            "A list of interface entries.  The number of
            entries is given by the value of IfNumber."
    ::= { JBODInfo 7 }
    
JBODHdEntry5 OBJECT-TYPE
    SYNTAX  HdEntryDef
    ACCESS  not-accessible
    STATUS  mandatory
    DESCRIPTION
            "An interface entry containing objects at the
            subnetwork layer and below for a particular
            interface."
    INDEX   { JBODHdIndex5 }
    ::= { JBODHdTable5 1 }
JBODHdEntry5Def ::=
    SEQUENCE {
        JBODHdIndex5  INTEGER,
        JBODHdDescr5 DisplayString,
        JBODHdTemperature5 DisplayString,
        JBODHdStatus5 INTEGER,
        JBODHdModel5 DisplayString,
        JBODHdCapacity5 DisplayString,
        JBODHdSmartInfo5 DisplayString
	}
JBODHdIndex5 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry5 1 }
JBODHdDescr5 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry5 2 }
JBODHdTemperature5 OBJECT-TYPE
    SYNTAX  DisplayString
    ACCESS  read-only
    STATUS  mandatory
    DESCRIPTION
            "Hard disk temperature."
    ::= { JBODHdEntry5 3 }
JBODHdStatus5 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry5 4 }
JBODHdModel5 OBJECT-TYPE
    SYNTAX  DisplayString
    ACCESS  read-only
    STATUS  mandatory
    DESCRIPTION "Hard disk model."
    ::= { JBODHdEntry5 5 }
JBODHdCapacity5 OBJECT-TYPE
    SYNTAX  DisplayString
    ACCESS  read-only
    STATUS  mandatory
    DESCRIPTION "Hard disk capacity."
    ::= { JBODHdEntry5 6 }
JBODHdSmartInfo5 OBJECT-TYPE
    SYNTAX  DisplayString
    ACCESS  read-only
    STATUS  mandatory
    DESCRIPTION "Hard disk SMART information."
    ::= { JBODHdEntry5 7 }
    
JBODHdTable6 OBJECT-TYPE
    SYNTAX  SEQUENCE OF HdEntryDef
    ACCESS  not-accessible
    STATUS  mandatory
    DESCRIPTION
            "A list of interface entries.  The number of
            entries is given by the value of IfNumber."
    ::= { JBODInfo 8 }
    
JBODHdEntry6 OBJECT-TYPE
    SYNTAX  HdEntryDef
    ACCESS  not-accessible
    STATUS  mandatory
    DESCRIPTION
            "An interface entry containing objects at the
            subnetwork layer and below for a particular
            interface."
    INDEX   { JBODHdIndex6 }
    ::= { JBODHdTable6 1 }
JBODHdEntry6Def ::=
    SEQUENCE {
        JBODHdIndex6  INTEGER,
        JBODHdDescr6 DisplayString,
        JBODHdTemperature6 DisplayString,
        JBODHdStatus6 INTEGER,
        JBODHdModel6 DisplayString,
        JBODHdCapacity6 DisplayString,
        JBODHdSmartInfo6 DisplayString
	}
JBODHdIndex6 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry6 1 }
JBODHdDescr6 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry6 2 }
JBODHdTemperature6 OBJECT-TYPE
    SYNTAX  DisplayString
    ACCESS  read-only
    STATUS  mandatory
    DESCRIPTION
            "Hard disk temperature."
    ::= { JBODHdEntry6 3 }
JBODHdStatus6 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry6 4 }
JBODHdModel6 OBJECT-TYPE
    SYNTAX  DisplayString
    ACCESS  read-only
    STATUS  mandatory
    DESCRIPTION "Hard disk model."
    ::= { JBODHdEntry6 5 }
JBODHdCapacity6 OBJECT-TYPE
    SYNTAX  DisplayString
    ACCESS  read-only
    STATUS  mandatory
    DESCRIPTION "Hard disk capacity."
    ::= { JBODHdEntry6 6 }
JBODHdSmartInfo6 OBJECT-TYPE
    SYNTAX  DisplayString
    ACCESS  read-only
    STATUS  mandatory
    DESCRIPTION "Hard disk SMART information."
    ::= { JBODHdEntry6 7 }
    
JBODHdTable7 OBJECT-TYPE
    SYNTAX  SEQUENCE OF HdEntryDef
    ACCESS  not-accessible
    STATUS  mandatory
    DESCRIPTION
            "A list of interface entries.  The number of
            entries is given by the value of IfNumber."
    ::= { JBODInfo 9 }
    
JBODHdEntry7 OBJECT-TYPE
    SYNTAX  HdEntryDef
    ACCESS  not-accessible
    STATUS  mandatory
    DESCRIPTION
            "An interface entry containing objects at the
            subnetwork layer and below for a particular
            interface."
    INDEX   { JBODHdIndex7 }
    ::= { JBODHdTable7 1 }
JBODHdEntry7Def ::=
    SEQUENCE {
        JBODHdIndex7  INTEGER,
        JBODHdDescr7 DisplayString,
        JBODHdTemperature7 DisplayString,
        JBODHdStatus7 INTEGER,
        JBODHdModel7 DisplayString,
        JBODHdCapacity7 DisplayString,
        JBODHdSmartInfo7 DisplayString
	}
JBODHdIndex7 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry7 1 }
JBODHdDescr7 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry7 2 }
JBODHdTemperature7 OBJECT-TYPE
    SYNTAX  DisplayString
    ACCESS  read-only
    STATUS  mandatory
    DESCRIPTION
            "Hard disk temperature."
    ::= { JBODHdEntry7 3 }
JBODHdStatus7 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry7 4 }
JBODHdModel7 OBJECT-TYPE
    SYNTAX  DisplayString
    ACCESS  read-only
    STATUS  mandatory
    DESCRIPTION "Hard disk model."
    ::= { JBODHdEntry7 5 }
JBODHdCapacity7 OBJECT-TYPE
    SYNTAX  DisplayString
    ACCESS  read-only
    STATUS  mandatory
    DESCRIPTION "Hard disk capacity."
    ::= { JBODHdEntry7 6 }
JBODHdSmartInfo7 OBJECT-TYPE
    SYNTAX  DisplayString
    ACCESS  read-only
    STATUS  mandatory
    DESCRIPTION "Hard disk SMART information."
    ::= { JBODHdEntry7 7 }
    
JBODHdTable8 OBJECT-TYPE
    SYNTAX  SEQUENCE OF HdEntryDef
    ACCESS  not-accessible
    STATUS  mandatory
    DESCRIPTION
            "A list of interface entries.  The number of
            entries is given by the value of IfNumber."
    ::= { JBODInfo 10 }
    
JBODHdEntry8 OBJECT-TYPE
    SYNTAX  HdEntryDef
    ACCESS  not-accessible
    STATUS  mandatory
    DESCRIPTION
            "An interface entry containing objects at the
            subnetwork layer and below for a particular
            interface."
    INDEX   { JBODHdIndex8 }
    ::= { JBODHdTable8 1 }
JBODHdEntry8Def ::=
    SEQUENCE {
        JBODHdIndex8  INTEGER,
        JBODHdDescr8 DisplayString,
        JBODHdTemperature8 DisplayString,
        JBODHdStatus8 INTEGER,
        JBODHdModel8 DisplayString,
        JBODHdCapacity8 DisplayString,
        JBODHdSmartInfo8 DisplayString
	}
JBODHdIndex8 OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { JBODHdEntry8 1 }
JBODHdDescr8 OBJECT-TYPE
    SYNTAX  DisplayString (SIZE (0..255))
    ACCESS  read-only
    STATUS  mandatory
    DESCRIPTION
            "A textual string containing information about the
            interface.  This string should include the name of
            the manufacturer, the product name and the version
            of the hardware interface."
    ::= { JBODHdEntry8 2 }
JBODHdTemperature8 OBJECT-TYPE
    SYNTAX  DisplayString
    ACCESS  read-only
    STATUS  mandatory
    DESCRIPTION
            "Hard disk temperature."
    ::= { JBODHdEntry8 3 }
JBODHdStatus8 OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { JBODHdEntry8 4 }
JBODHdModel8 OBJECT-TYPE
    SYNTAX  DisplayString
    ACCESS  read-only
    STATUS  mandatory
    DESCRIPTION "Hard disk model."
    ::= { JBODHdEntry8 5 }
JBODHdCapacity8 OBJECT-TYPE
    SYNTAX  DisplayString
    ACCESS  read-only
    STATUS  mandatory
    DESCRIPTION "Hard disk capacity."
    ::= { JBODHdEntry8 6 }
JBODHdSmartInfo8 OBJECT-TYPE
    SYNTAX  DisplayString
    ACCESS  read-only
    STATUS  mandatory
    DESCRIPTION "Hard disk SMART information."
    ::= { JBODHdEntry8 7 }
    
 -- system inform Ex
	SystemInfoEx        OBJECT IDENTIFIER ::= { storageSystem 3 }

	SystemCPU-UsageEX OBJECT-TYPE
		SYNTAX Integer32
    	MAX-ACCESS read-only
	    STATUS     current
    	DESCRIPTION
			"System CPU usage"
		::= { SystemInfoEx 1 }
	SystemTotalMemEX OBJECT-TYPE
		SYNTAX Counter64
    	MAX-ACCESS read-only
	    STATUS     current
    	DESCRIPTION
			"System total memory in byte"
		::= { SystemInfoEx 2 }
	SystemFreeMemEX OBJECT-TYPE
		SYNTAX Counter64
    	MAX-ACCESS read-only
	    STATUS     current
    	DESCRIPTION
			"System free memory in byte"
		::= { SystemInfoEx 3 }
	SystemUptimeEX OBJECT-TYPE
    	SYNTAX     TimeTicks
    	MAX-ACCESS read-only
	    STATUS     current
    	DESCRIPTION
        	"The amount of time since this host was last
	        initialized.  Note that this is different from
    	    sysUpTime in the SNMPv2-MIB [RFC1907] because
        	sysUpTime is the uptime of the network management
	        portion of the system."
    	::= { SystemInfoEx 4 }
	CPU-TemperatureEX OBJECT-TYPE
		SYNTAX Integer32
    	MAX-ACCESS read-only
	    STATUS     current
    	DESCRIPTION
			"CPU temperature in centigrade"
		::= { SystemInfoEx 5 }
	SystemTemperatureEX OBJECT-TYPE
		SYNTAX Integer32
    	MAX-ACCESS read-only
	    STATUS     current
    	DESCRIPTION
			"System temperature in centigrade"
		::= { SystemInfoEx 6 }

IfNumberEX OBJECT-TYPE
    SYNTAX  INTEGER
    ACCESS  read-only
    STATUS  mandatory
    DESCRIPTION
            "The number of network interfaces (regardless of
            their current state) present on this system."
    ::= { SystemInfoEx 8 }
SystemIfTableEx OBJECT-TYPE
    SYNTAX  SEQUENCE OF IfEntryExDef
    ACCESS  not-accessible
    STATUS  mandatory
    DESCRIPTION
            "A list of interface entries.  The number of
            entries is given by the value of IfNumber."
    ::= { SystemInfoEx 9 }
IfEntryEx OBJECT-TYPE
    SYNTAX  IfEntryExDef
    ACCESS  not-accessible
    STATUS  mandatory
    DESCRIPTION
            "An interface entry containing objects at the
            subnetwork layer and below for a particular
            interface."
    INDEX   { IfIndexEX }
    ::= { SystemIfTableEx 1 }
IfEntryExDef ::=
    SEQUENCE {
        IfIndexEX
            INTEGER,
        IfDescrEX
            DisplayString,
		IfPacketsReceivedEX
            Counter,
		IfPacketsSentEX
            Counter,
		IfErrorPacketsEX
            Counter
	}
IfIndexEX OBJECT-TYPE
    SYNTAX  INTEGER
    ACCESS  read-only
    STATUS  mandatory
    DESCRIPTION
            "A unique value for each interface.  Its value
            ranges between 1 and the value of IfNumber.  The
            value for each interface must remain constant at
            least from one re-initialization of the entity's
            network management system to the next re-
            initialization."
    ::= { IfEntryEx 1 }
IfDescrEX OBJECT-TYPE
    SYNTAX  DisplayString (SIZE (0..255))
    ACCESS  read-only
    STATUS  mandatory
    DESCRIPTION
            "A textual string containing information about the
            interface.  This string should include the name of
            the manufacturer, the product name and the version
            of the hardware interface."
    ::= { IfEntryEx 2 }
IfPacketsReceivedEX OBJECT-TYPE
    SYNTAX  Counter
    ACCESS  read-only
    STATUS  mandatory
    DESCRIPTION
            "System packets received."
    ::= { IfEntryEx 3 }
IfPacketsSentEX OBJECT-TYPE
    SYNTAX  Counter
    ACCESS  read-only
    STATUS  mandatory
    DESCRIPTION
            "System packets sent."
    ::= { IfEntryEx 4 }
IfErrorPacketsEX OBJECT-TYPE
    SYNTAX  Counter
    ACCESS  read-only
    STATUS  mandatory
    DESCRIPTION
            "System error packets."
    ::= { IfEntryEx 5 }

HdNumberEX OBJECT-TYPE
    SYNTAX  INTEGER
    ACCESS  read-only
    STATUS  mandatory
    DESCRIPTION
            "The number of hard drive slots."
    ::= { SystemInfoEx 10 }
SystemHdTableEX OBJECT-TYPE
    SYNTAX  SEQUENCE OF HdEntryExDef
    ACCESS  not-accessible
    STATUS  mandatory
    DESCRIPTION
            "A list of interface entries.  The number of
            entries is given by the value of HdNumber."
    ::= { SystemInfoEx 11 }
HdEntryEx OBJECT-TYPE
    SYNTAX  HdEntryExDef
    ACCESS  not-accessible
    STATUS  mandatory
    DESCRIPTION
            "An interface entry containing objects at the
            subnetwork layer and below for a particular
            interface."
    INDEX   { HdIndex }
    ::= { SystemHdTableEX 1 }
HdEntryExDef ::=
    SEQUENCE {
        HdIndexEX
            INTEGER,
        HdDescrEX
            DisplayString,
        HdTemperatureEX
            Integer32,
        HdStatusEX
            INTEGER,
	HdModelEX DisplayString,
	HdCapacityEX Counter64,
	HdSmartInfoEX DisplayString
	}
HdIndexEX OBJECT-TYPE
    SYNTAX  INTEGER
    ACCESS  read-only
    STATUS  mandatory
    DESCRIPTION
            "A unique value for each hard disk.  Its value
            ranges between 1 and the value of IfNumber.  The
            value for each interface must remain constant at
            least from one re-initialization of the entity's
            network management system to the next re-
            initialization."
    ::= { HdEntryEx 1 }
HdDescrEX OBJECT-TYPE
    SYNTAX  DisplayString (SIZE (0..255))
    ACCESS  read-only
    STATUS  mandatory
    DESCRIPTION
            "A textual string containing information about the
            interface.  This string should include the name of
            the manufacturer, the product name and the version
            of the hardware interface."
    ::= { HdEntryEx 2 }
HdTemperatureEX OBJECT-TYPE
    SYNTAX  Integer32
    ACCESS  read-only
    STATUS  mandatory
    DESCRIPTION
            "Hard disk temperature in centigrade."
    ::= { HdEntryEx 3 }
HdStatusEX OBJECT-TYPE
    SYNTAX     INTEGER {
	ready(0),
	noDisk(-5),
	invalid(-6),
	rwError(-9),
	unknown(-4)
	}
    ACCESS  read-only
    STATUS  mandatory
    DESCRIPTION
            "HDD status. 0:not availible, 1:availible."
    ::= { HdEntryEx 4 }
HdModelEX OBJECT-TYPE
    SYNTAX  DisplayString
    ACCESS  read-only
    STATUS  mandatory
    DESCRIPTION "Hard disk model."
    ::= { HdEntryEx 5 }
HdCapacityEX OBJECT-TYPE
    SYNTAX  Counter64
    ACCESS  read-only
    STATUS  mandatory
    DESCRIPTION "Hard disk capacity in byte."
    ::= { HdEntryEx 6 }
HdSmartInfoEX OBJECT-TYPE
    SYNTAX  DisplayString
    ACCESS  read-only
    STATUS  mandatory
    DESCRIPTION "Hard disk SMART information."
    ::= { HdEntryEx 7 }

	ModelNameEX OBJECT-TYPE
		SYNTAX DisplayString
    	MAX-ACCESS read-only
	    STATUS     current
    	DESCRIPTION
			"Model name"
		::= { SystemInfoEx 12 }
	HostNameEX OBJECT-TYPE
		SYNTAX DisplayString
    	MAX-ACCESS read-only
	    STATUS     current
    	DESCRIPTION
			"Model name"
		::= { SystemInfoEx 13 }

SysFanNumberEX OBJECT-TYPE
    SYNTAX  INTEGER
    ACCESS  read-only
    STATUS  mandatory
    DESCRIPTION
            "The number of system fan (regardless of
            their current state) present on this system."
    ::= { SystemInfoEx 14 }
SystemFanTableEx OBJECT-TYPE
    SYNTAX  SEQUENCE OF SysFanEntryExDef
    ACCESS  not-accessible
    STATUS  mandatory
    DESCRIPTION
            "A list of interface entries.  The number of
            entries is given by the value of SysFanNumber."
    ::= { SystemInfoEx 15 }
SysFanEntryEx OBJECT-TYPE
    SYNTAX  SysFanEntryExDef
    ACCESS  not-accessible
    STATUS  mandatory
    DESCRIPTION
            "An system fan entry containing objects at the
            subnetwork layer and below for a particular
            interface."
    INDEX   { SysFanIndexEX }
    ::= { SystemFanTableEx 1 }
SysFanEntryExDef ::=
    SEQUENCE {
        SysFanIndexEX
            INTEGER,
        SysFanDescrEX
            DisplayString,
		SysFanSpeedEX
            Integer32
	}
SysFanIndexEX OBJECT-TYPE
    SYNTAX  INTEGER
    ACCESS  read-only
    STATUS  mandatory
    DESCRIPTION
            "A unique value for each system fan. Its value
            ranges between 1 and the value of SysFanNumber.  The
            value for each interface must remain constant at
            least from one re-initialization of the entity's
            network management system to the next re-
            initialization."
    ::= { SysFanEntryEx 1 }
SysFanDescrEX OBJECT-TYPE
    SYNTAX  DisplayString (SIZE (0..255))
    ACCESS  read-only
    STATUS  mandatory
    DESCRIPTION
            "A textual string containing information about the
            interface.  This string should include the name of
            the manufacturer, the product name and the version
            of the hardware interface."
    ::= { SysFanEntryEx 2 }
SysFanSpeedEX OBJECT-TYPE
    SYNTAX  Integer32
    ACCESS  read-only
    STATUS  mandatory
    DESCRIPTION
            "System fan speed (RPM)."
    ::= { SysFanEntryEx 3 }

SysVolumeNumberEX OBJECT-TYPE
    SYNTAX  INTEGER
    ACCESS  read-only
    STATUS  mandatory
    DESCRIPTION
            "The number of system volumes (regardless of
            their current state) present on this system."
    ::= { SystemInfoEx 16 }
SystemVolumeTableEx OBJECT-TYPE
    SYNTAX  SEQUENCE OF SysVolumeEntryExDef
    ACCESS  not-accessible
    STATUS  mandatory
    DESCRIPTION
            "A list of volume entries.  The number of
            entries is given by the value of SysVolumeNumber."
    ::= { SystemInfoEx 17 }
SysVolumeEntryEx OBJECT-TYPE
    SYNTAX  SysVolumeEntryExDef
    ACCESS  not-accessible
    STATUS  mandatory
    DESCRIPTION
            "An system volume entry"
    INDEX   { SysVolumeIndexEX }
    ::= { SystemVolumeTableEx 1 }
SysVolumeEntryExDef ::=
    SEQUENCE {
        SysVolumeIndexEX	INTEGER,
        SysVolumeDescrEX	DisplayString,
	SysVolumeFSEX	DisplayString,
	SysVolumeTotalSizeEX	Counter64,
	SysVolumeFreeSizeEX	Counter64,
	SysVolumeStatusEX	DisplayString
	}
SysVolumeIndexEX OBJECT-TYPE
    SYNTAX  INTEGER
    ACCESS  read-only
    STATUS  mandatory
    DESCRIPTION
            "A unique value for each system volume. Its value
            ranges between 1 and the value of SysVolumeNumber.  The
            value for each volume must remain constant at
            least from one re-initialization of the entity's
            volume system to the next re-initialization."
    ::= { SysVolumeEntryEx 1 }
SysVolumeDescrEX OBJECT-TYPE
    SYNTAX  DisplayString (SIZE (0..255))
    ACCESS  read-only
    STATUS  mandatory
    DESCRIPTION	"A textual string containing information about the volume."
    ::= { SysVolumeEntryEx 2 }
SysVolumeFSEX OBJECT-TYPE
    SYNTAX  DisplayString (SIZE (0..15))
    ACCESS  read-only
    STATUS  mandatory
    DESCRIPTION	"System Volume file system."
    ::= { SysVolumeEntryEx 3 }
SysVolumeTotalSizeEX OBJECT-TYPE
    SYNTAX  Counter64
    ACCESS  read-only
    STATUS  mandatory
    DESCRIPTION	"System Volume total size in byte."
    ::= { SysVolumeEntryEx 4 }
SysVolumeFreeSizeEX OBJECT-TYPE
    SYNTAX  Counter64
    ACCESS  read-only
    STATUS  mandatory
    DESCRIPTION	"System Volume free size in byte."
    ::= { SysVolumeEntryEx 5 }
SysVolumeStatusEX OBJECT-TYPE
    SYNTAX  DisplayString (SIZE (0..255))
    ACCESS  read-only
    STATUS  mandatory
    DESCRIPTION	"System Volume status."
    ::= { SysVolumeEntryEx 6 }
END
